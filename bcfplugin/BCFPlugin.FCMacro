__Name__ = "BCF-Plugin"
__Comment__ = "Lets you open and operate on BCF file in FreeCAD"
__License__ = "LGPL-2.1"
__Web__ = "https://github.com/podestplatz/BCF-Plugin-FreeCAD"
__Wiki__ = "https://github.com/podestplatz/BCF-Plugin-FreeCAD/wiki/Home"
__Icon__ = ""
__Help__ = "Let's"
__Author__ = "Patrick Podest"
__Version__ = ""
__Status__ = "Alpha"
__Requires__ = "FreeCAD >= 0.18"
__Communication__ = "https://github.com/podestplatz/BCF-Plugin-FreeCAD/issues"


import bcfplugin
import bcfplugin.BCFPlugin as plugin

import FreeCAD
FreeCAD.addImportType("BCF-Document (*.bcf *.bcfzip)",
    "bcfplugin.filehandlers")

plugin.start()
