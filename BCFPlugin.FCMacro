"""
Copyright (C) 2019 PODEST Patrick 

This library is free software; you can redistribute it and/or
modify it under the terms of the GNU Lesser General Public
License as published by the Free Software Foundation; either
version 2.1 of the License, or (at your option) any later version.

This library is distributed in the hope that it will be useful,
but WITHOUT ANY WARRANTY; without even the implied warranty of
MERCHANTABILITY or FITNESS FOR A PARTICULAR PURPOSE.  See the GNU
Lesser General Public License for more details.

You should have received a copy of the GNU Lesser General Public
License along with this library; if not, write to the Free Software
Foundation, Inc., 51 Franklin Street, Fifth Floor, Boston, MA  02110-1301  USA
"""

"""
Author: Patrick Podest
Date: 2019-08-16
Github: @podestplatz

**** Description ****
This file builds the entry point for FreeCAD into the plugin. It also adds BCF
files as new import type to FreeCAD. 
"""

__Name__ = "BCF-Plugin"
__Comment__ = "Lets you open and operate on BCF file in FreeCAD"
__License__ = "LGPL-2.1"
__Web__ = "https://github.com/podestplatz/BCF-Plugin-FreeCAD"
__Wiki__ = "https://github.com/podestplatz/BCF-Plugin-FreeCAD/wiki/Home"
__Icon__ = "BCFPlugin.svg"
__Help__ = ""
__Author__ = "Patrick Podest"
__Version__ = "1.0.1"
__Status__ = "Beta"
__Requires__ = "FreeCAD >= 0.18"
__Communication__ = "https://github.com/podestplatz/BCF-Plugin-FreeCAD/issues"


import bcfplugin
import bcfplugin.BCFPlugin as plugin

import FreeCAD
FreeCAD.addImportType("BCF-Document (*.bcf *.bcfzip)",
    "bcfplugin.filehandlers")

plugin.start()
